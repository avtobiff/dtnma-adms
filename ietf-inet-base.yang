module ietf-inet-base {
  yang-version 1.1;
  namespace "ari://ietf/inet-base/";
  prefix inet-base;

  import ietf-amm {
    prefix amm;
  }
  import ietf-amm-base {
    prefix amm-base;
  }
  import ietf-network-base {
    prefix network-base;
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>";
  description
    "This module implements the DTN Management Architecture (DTNMA)
     Agent core functionality.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2025-07-03 {
    description
      "Updated for latest ADM document.";
    reference
      "draft-ietf-dtn-adm-yang";
  }

  amm:amm;

  amm:enum 4;

  // Display hints
  identity display-bstr-ipaddress {
    amm:enum 2;
    description
      "Interpret byte string values as either IPv4 address (4-octet
       length) or IPv6 address (16-octet length) and display as
       human-friendly text according to RFC 4001 conventions.";
    reference
      "RFC 4001: Textual Conventions for Internet Network Addresses";
    base amm-type:display-hint-bstr;
  }

  // Data types
  typedef ipv4-address {
    amm:enum 0;
    description
      "The ipv4-address type represents an IPv4 address in binary
       form. This form always uses exactly 4 bytes to encode address
       values.";
    reference
      "RFC 791: Internet Protocol";
    type ari:bytestr {
      amm:display-hint display-bstr-ipaddress;
      length "4";
    }
  }
  typedef ipv6-address {
    amm:enum 1;
    description
      "The ipv6-address type represents an IPv6 address in binary
       form. This form always uses exactly 16 bytes to encode address
       values.";
    reference
      "RFC 4291: IP Version 6 Addressing Architecture";
    type ari:bytestr {
      amm:display-hint display-bstr-ipaddress;
      length "16";
    }
  }
  typedef ip-address {
    amm:enum 2;
    description
      "This type represents either an IPv4 or IPv6 address, which is
       distinguished by each having a specific valid length.";
    type union {
      type ipv4-address;
      type ipv6-address;
    }
  }
  typedef zone {
    amm:enum 4;
    description
      "The zone index is used to disambiguate identical address
       values.  For link-local addresses, the zone index will
       typically be the interface index number or the name of an
       interface.  If the zone index is not present, the default
       zone of the device will be used.

       The canonical format for the zone index is the numerical
       form.";
    reference
      "RFC 4007: IPv6 Scoped Address Architecture
       RFC 4001: Textual Conventions for Internet Network Addresses";
    type union {
      type ari:uint;
      type ari:textstr;
    }
  }
  typedef port-number {
    amm:enum 3;
    description
      "The port-number type represents a 16-bit port number of an
       Internet transport-layer protocol such as UDP, TCP, DCCP, or
       SCTP.  Port numbers are assigned by IANA.  A current list of
       all assignments is available from <http://www.iana.org/>.

       Note that the port number value zero is reserved by IANA.  In
       situations where the value zero does not make sense, it can
       be excluded by subtyping the port-number type.
       In the value set and its semantics, this type is equivalent
       to the InetPortNumber textual convention of the SMIv2 and
       the inet:port-number of NETMOD.";
    reference
      "RFC  768: User Datagram Protocol
       RFC  793: Transmission Control Protocol
       RFC 4960: Stream Control Transmission Protocol
       RFC 4340: Datagram Congestion Control Protocol (DCCP)
       RFC 4001: Textual Conventions for Internet Network Addresses";
    type ari:uint {
      length "0..65535";
    }
  }
  typedef domain-name {
    amm:enum 5;
    description
      "The domain-name type represents a DNS domain name.  The
       name SHOULD be fully qualified whenever possible.

       Internet domain names are only loosely specified.  Section
       3.5 of RFC 1034 recommends a syntax (modified in Section
       2.1 of RFC 1123).  The pattern above is intended to allow
       for current practice in domain name use, and some possible
       future expansion.  It is designed to hold various types of
       domain names, including names used for A or AAAA records
       (host names) and other records, such as SRV records.  Note
       that Internet host names have a stricter syntax (described
       in RFC 952) than the DNS recommendations in RFCs 1034 and
       1123, and that systems that want to store host names in
       schema nodes using the domain-name type are recommended to
       adhere to this stricter standard to ensure interoperability.
       The encoding of DNS names in the DNS protocol is limited
       to 255 characters.  Since the encoding consists of labels
       prefixed by a length bytes and there is a trailing NULL
       byte, only 253 characters can appear in the textual dotted
       notation.

       The description clause of schema nodes using the domain-name
       type MUST describe when and how these names are resolved to
       IP addresses.  Note that the resolution of a domain-name value
       may require to query multiple DNS records (e.g., A for IPv4
       and AAAA for IPv6).  The order of the resolution process and
       which DNS record takes precedence can either be defined
       explicitly or may depend on the configuration of the
       resolver.

       Domain-name values use the US-ASCII encoding.  Their canonical
       format uses lowercase US-ASCII characters.  Internationalized
       domain names MUST be A-labels as per RFC 5890.";
    reference
      "RFC  952: DoD Internet Host Table Specification
       RFC 1034: Domain Names - Concepts and Facilities
       RFC 1123: Requirements for Internet Hosts -- Application
                 and Support
       RFC 2782: A DNS RR for specifying the location of services
                 (DNS SRV)
       RFC 5890: Internationalized Domain Names in Applications
                 (IDNA): Definitions and Document Framework";
    type ari:textstr {
      pattern '('
            + '(([a-zA-Z0-9_]([a-zA-Z0-9\-_]){0,61})?[a-zA-Z0-9]\.)*'
            + '([a-zA-Z0-9_]([a-zA-Z0-9\-_]){0,61})?[a-zA-Z0-9]\.?'
            + ')|\.';
      length "1..253";
    }
  }

  // Endpoint types for IP
  identity ip-endpoint {
    amm:enum 0;
    description
      "This object defines parameters for an IP endpoint
       independent of any possible transport above the network
       layer.";
    base "//ietf/network-base/ident/abstract-endpoint";
    amm:parameter address {
      description
        "The endpoint network address.";
      type ip-address;
    }
    amm:parameter zone {
      description
        "The optional zone used to interpret the address.";
      default "null";
      type union {
        type zone;
        type ari:null;
      }
    }
  }
  identity ip-transport {
    amm:enum 1;
    description
      "This object defines parameters for any IP-based transport
       protocol which uses a 16-bit port number, as seen from outside
       of the IP node.
       This is different from parameters necessary to bind a
       transport from within that IP node, which might include
       additional information.";
    base "//ietf/network-base/ident/abstract-endpoint";
    amm:parameter address {
      description
        "The endpoint network address.";
      type ip-address;
    }
    amm:parameter port {
      description
        "The transport layer port number.";
      type port-number;
    }
    amm:parameter zone {
      description
        "The optional zone used to interpret the address.";
      default "null";
      type union {
        type zone;
        type ari:null;
      }
    }
  }

  // Pattern matching predicates
  amm:oper match-ip-vlsm {
    amm:enum 0;
    description
      "This is a unary predicate operator which will compare an
       IP address operand based on concepts of variable-length
       subnet masking (VLSM) from Classless Inter-domain Routing
       (CIDR) definitions.
       This representation does not use the text form of CIDR
       notation to avoid processors needing to parse text content.

       This form of pattern can only match 'ip-endpoint' or
       'ip-transport' references.

       Because of the limitations of VLSM, each reference to this
       object can only represent a single contiguous, bit-aligned
       IP block. Not all possible blocks can be represented by a
       single VLSM pattern.";
    reference
      "RFC 4632: Classless Inter-domain Routing (CIDR)
       RFC 4291: IPv6 Addressing Architecture";
    amm:parameter base {
      description
        "The base address for the subnet mask.";
      type ip-address;
    }
    amm:parameter prefix {
      description
        "The number of prefix bits for the subnet mask.
         When the base address is IPv4 the prefix SHALL be
         limited to no larger than 32.";
      type ari:uint {
        range "0..128";
      }
    }
    amm:operand value {
      description
        "The value to check for a match.";
      type union {
        // raw address bytes
        type ip-address;
        // address-as-parameter
        type identityref {
          base ip-endpoint;
        }
        type identityref {
          base ip-transport;
        }
      }
    }
    amm:result is-match {
      description
        "The result is true if the value matches the given pattern.";
      type ari:bool;
    }
  }
}
