module ietf-amm-base {
  yang-version 1.1;
  namespace "ari://ietf/amm-base/";
  prefix amm-type;

  import ietf-amm {
    prefix amm;
  }

  import ietf-ari-types {
    prefix ari;
    reference
      "draft-ietf-dtn-adm-yang";
  }

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>
     Editor: Per Andersson
             <mailto:per@ionio.se>";
  description
    "This module defines base IDENT objects and base TYPEDEF
     objects for the AMM.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2025-07-03 {
    description
      "Updated for latest ADM document.";
    reference
      "draft-ietf-dtn-adm-yang";
  }
  amm:enum 25;

  amm:amm;

  // abstract display hint hierarchy
  identity display-hint {
    amm:enum 0;
    description
      "The base IDENT for objects usable as arguments for the
       'amm:display-hint' extension.
       This object itself provides no display hint purpose.";
    amm:abstract true;
  }
  identity display-hint-integer {
    amm:enum 1;
    description
      "Intermediate base IDENT of display hints for integer values.
       Hints derived from this object SHALL only apply to built-in
       types BYTE, INT, UINT, VAST, and UVAST.";
    amm:abstract true;
    base display-hint;
  }
  identity display-hint-float {
    amm:enum 2;
    description
      "Intermediate base IDENT of display hints for floating point
       values.
       Hints derived from this object SHALL only apply to built-in
       types REAL32 and REAL64.";
    amm:abstract true;
    base display-hint;
  }
  identity display-hint-bstr {
    amm:enum 3;
    description
      "Intermediate base IDENT of display hints for byte string
       values.
       Hints derived from this object SHALL only apply to built-in
       type BYTESTR.";
    amm:abstract true;
    base display-hint;
  }
  identity display-hint-time {
    amm:enum 4;
    description
      "Intermediate base IDENT of display hints for time values.
       Hints derived from this object SHALL only apply to built-in
       types TP and TD.";
    amm:abstract true;
    base display-hint;
  }

  // Named type unions
  typedef type-ref {
    amm:enum 0;
    description
      "Reference to either a built-in type or a TYPEDEF object.";
    type union {
      type ari:aritype;
      type amm:typedef;
    }
  }
  typedef integer {
    amm:enum 1;
    description
      "Any type which represents a discrete integer.
       This union order prefers smaller range and signed types.";
    type union {
      type ari:byte;
      type ari:int;
      type ari:uint;
      type ari:vast;
      type ari:uvast;
    }
  }
  typedef float {
    amm:enum 2;
    description
      "Any type which represents a floating point number.
       This union order prefers smaller range.";
    type union {
      type ari:real32;
      type ari:real64;
    }
  }
  typedef numeric {
    amm:enum 3;
    description
      "Any type which can be used with numeric expressions.";
    type union {
      type ari:integer;
      type ari:float;
    }
  }
  typedef numeric-or-time {
    amm:enum 27;
    description
      "Any type which can be used with numeric or time-as-numeric
       expressions.";
    type union {
      type ari:numeric;
      type time;
    }
  }
  typedef primitive {
    amm:enum 4;
    description
      "Any primitive type.
       This union order prefers conversion to wide types.";
    type union {
      type ari:numeric;
      type ari:textstr;
      type ari:bytestr;
      type ari:bool;
      // null is last option for conversion
      type ari:null;
    }
  }
  typedef time {
    amm:enum 5;
    description
      "Any type which can be used with time expressions.";
    type union {
      type ari:tp;
      type ari:td;
    }
  }
  typedef simple {
    amm:enum 6;
    description
      "Any type which contains a single literal value (not nested).";
    type union {
      type time;
      type ari:primitive;
    }
  }
  typedef nested {
    amm:enum 7;
    description
      "A literal type which contains other ARI values.";
    type union {
      type amm:ac;
      type amm:am;
      type amm:tbl;
    }
  }
  typedef any {
    amm:enum 8;
    description
      "Any value representable by an ARI.";
    // These type names are built-in
    type union {
      type amm:literal;
      type ari:object;
    }
  }
  typedef value-obj {
    amm:enum 9;
    description
      "A reference to an object which can produce a value.";
    type union {
      type ari:const;
      type ari:edd;
      type ari:var;
    }
  }
  typedef nonce {
    amm:enum 10;
    description
      "This type union is used to correlate Agent-Manager messages.
       The union is defined in Section 4.2.5 of draft-ietf-dtn-amm.";
    reference
      "draft-ietf-dtn-amm";
    type union {
      type ari:bytestr;
      type ari:uvast;
      type ari:null;
    }
  }
  typedef id-text {
    amm:enum 25;
    description
      "This type is used to define and match object text names.
       The type is defined in Section 4.2.5 of draft-ietf-dtn-amm.";
    reference
      "draft-ietf-dtn-amm";
    type ari:textstr {
      pattern '!?[A-Za-z_][0-9A-Za-z_\-\.]*';
    }
  }
  typedef id-int {
    amm:enum 26;
    description
      "This type is used to define and match object integer
       enumerations.
       The type is defined in Section 4.2.5 of draft-ietf-dtn-amm.";
    reference
      "draft-ietf-dtn-amm";
    type ari:int;
  }

  // operational semantic types
  typedef counter32 {
    amm:enum 11;
    description
      "A 32-bit counter with an arbitrary initial value which can
       only increment and never decrement.
       When the value reaches the upper limit of the type it wraps
       around to zero.
       At least two samples of this value need to be compared over
       time to be meaningful.
       This type is consistent with the SMIv2 and YANG data types
       of the same name.";
    reference
      "RFC 2578: Structure of Management Information Version 2
       RFC 6021: Common YANG Data Types";
    type ari:uint;
  }
  typedef counter64 {
    amm:enum 12;
    description
      "A 64-bit counter with an arbitrary initial value which can
       only increment and never decrement.
       When the value reaches the upper limit of the type it wraps
       around to zero.
       At least two samples of this value need to be compared over
       time to be meaningful.
       This type is consistent with the SMIv2 and YANG data types
       of the same name.";
    reference
      "RFC 2578: Structure of Management Information Version 2
       RFC 6021: Common YANG Data Types";
    type ari:uvast;
  }
  typedef gauge32 {
    amm:enum 13;
    description
      "A 32-bit value sampling some quantized measurement.
       The value can increase or decrease arbitrarily over time.
       This type is consistent with the SMIv2 and YANG data types
       of the same name.";
    reference
      "RFC 2578: Structure of Management Information Version 2
       RFC 6021: Common YANG Data Types";
    type ari:int;
  }
  typedef gauge64 {
    amm:enum 14;
    description
      "A 64-bit value sampling some quantized measurement.
       The value can increase or decrease arbitrarily over time.
       This type is consistent with the SMIv2 and YANG data types
       of the same name.";
    reference
      "RFC 2578: Structure of Management Information Version 2
       RFC 6021: Common YANG Data Types";
    type ari:vast;
  }
  typedef timestamp {
    amm:enum 15;
    description
      "A time point representing the system clock at which a specific
       occurrence happened.
       The specific occurrence must be defined in the description
       of any node defined using this type.
       This type is consistent with the SMIv2 and YANG data types
       of the same name.";
    reference
      "RFC 2579: Textual Conventions for SMIv2
       RFC 6021: Common YANG Data Types";
    type ari:tp;
  }

  // Restrictions on AC item types for Evaluation and EXPR
  typedef eval-tgt {
    amm:enum 16;
    description
      "A value which can be the target of an evaluation.
       An inline <./typedef/expr> value is evaluated directly.
       A reference to a value-producing object is dereferenced and
       SHALL produce a value that matches <./typedef/expr>, which
       is then evaluated.";
    type union {
      // object which produces an expression
      type value-obj;
      // inline expression
      type expr;
    }
  }
  typedef expr-item {
    amm:enum 17;
    description
      "Each item of an EXPR list.";
    type union {
      // plain value for the stack
      type amm:literal;
      // object which produces a value for the stack
      type value-obj;
      // operator to evaluate
      type ari:oper;
    }
  }
  typedef expr {
    amm:enum 18;
    description
      "The contents of an EXPR container.";
    amm:ulist {
      type expr-item;
    }
  }

  // Restrictions on AC item types for Execution and MAC
  typedef exec-tgt {
    amm:enum 19;
    description
      "A value which can be the target of an execution.
       An inline <./typedef/mac> value is expanded and executed.
       A reference to a value-producing object is dereferenced and
       SHALL produce a value that matches <./typedef/exec-tgt>,
       which is then executed.
       A reference to a CTRL is executed directly.";
    type union {
      type exec-item;
      // inline MAC
      type mac;
    }
  }
  typedef exec-item {
    amm:enum 20;
    description
      "A reference to an object which can be executed.
       The value-object must be typed to contain a
       <./typedef/exec-tgt>.";
    type union {
      type ari:ctrl;
      // object which produces an exec-tgt
      type value-obj;
    }
  }
  typedef mac {
    amm:enum 21;
    description
      "The contents of a MAC container are an ordered list of
       executable values.";
    amm:ulist {
      type exec-item;
    }
  }

  // Restrictions on AC item types for Reporting and RPTT
  typedef rpt-tgt {
    amm:enum 22;
    description
      "A value which can be the target of reporting.";
    type union {
      // object which produces an RPTT
      type value-obj;
      // inline RPTT
      type rptt;
    }
  }
  typedef rptt-item {
    amm:enum 23;
    description
      "Each item of a RPTT.
       Each item references a value-producing object or contains an
       expression to be evaluated.";
    type union {
      // produces the report item
      type value-obj;
      // evaluates to the report item
      type expr;
    }
  }
  typedef rptt {
    amm:enum 24;
    description
      "The contents of a report template, encoded as the sequence
       of template items.";
    amm:ulist {
      type rptt-item;
    }
  }
}
