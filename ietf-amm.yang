module ietf-amm {
  yang-version 1.1;
  namespace "ari://ietf/amm/";
  prefix amm;

  organization
    "Internet Engineering Task Force (IETF)" {
    amm:enum 1;
  }
  contact
    "WG Web: <http://tools.ietf.org/wg/dtn/>
     WG List: <mailto:dtn@ietf.org>

     Editor: Brian Sipos
             <mailto:brian.sipos+ietf@gmail.com>
     Editor: Per Andersson
             <mailto:per@ionio.se>";
  description
    "This module defines the DTN Management Architecture (DTNMA)
     Application Management Model (AMM) extensions within YANG.
     It also defines the base IDENT and TYPEDEF objects for the AMM.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";
  reference
    "draft-ietf-dtn-adm-yang";

  revision 2025-07-03 {
    description
      "Updated for latest ADM document.";
    reference
      "draft-ietf-dtn-adm-yang";
  }

  /*
   * This section contains extensions for common behavior of AMM
   * objects.
   */

  extension amm {
    description
      "Indication that the YANG module is an ADM YANG module.";
  }

  extension enum {
    argument value;
    description
      "An enumeration identifies an object within a namespace.
       The argument to this statement is the integer value.";
  }

  extension typedef {
    argument name;
    description
      "The type for using a TYPEDEF as a value's type within an ADM.
       The argument to this statement is the object name.";
  }

  extension ac {
    argument name;
    description
      "The type for using an AC as a value's type within an ADM.
       The argument to this statement is the object name.";
  }

  extension am {
    argument name;
    description
      "The type for using an AM as a value's type within an ADM.
       The argument to this statement is the object name.";
  }

  extension tbl {
    argument name;
    description
      "The type for using an TBL as a value's type within an ADM.
       The argument to this statement is the object name.";
  }

  extension literal {
    description
      "The type for using a LITERAL as a value's type within an ADM.";
  }

  extension parameter {
    argument name;
    description
      "The schema for a formal parameter of an object.
       Order of parameters is significant within this statement.";
  }

  extension init-value {
    argument value;
    description
      "The literal value of a CONST object,
       initial state for a VAR object.
       The argument is the text form of the ARI";
  }

  extension init-expr {
    argument expr;
    description
      "An expression evaluated to initialize a VAR object.
       The argument is the text form of the EXPR AC";
  }

  /*
   * This section contains extensions for AMM object definitions.
   */

  extension abstract {
    argument is-abstract;
    description
      "The boolean abstract marking of an IDENT object.

       This means it is used in 'identity' statements in ADM YANG.";
  }

  extension const {
    argument name;
    description
      "Definition of a CONST within an ADM.
       The argument to this statement is the object name.
       An 'init-value' substatement must be present.";
  }

  extension ctrl {
    argument name;
    description
      "Definition of a CTRL within an ADM.
       The argument to this statement is the object name.";
  }

  extension result {
    argument name;
    description
      "A result value reported as a response to a control.
       The substatement is the result type.
       Each CTRL can have a single optional result.";
  }

  extension edd {
    argument name;
    description
      "Definition of an EDD within an ADM.
       The argument to this statement is the object name.";
  }

  extension oper {
    argument name;
    description
      "Definition of an OPER within an ADM.
       The argument to this statement is the object name.";
  }

  extension operand {
    argument name;
    description
      "An individual operand taken from the expression stack
       during evaluation of the OPER.
       Each substatement is an operand as a leaf (ARI).
       The order of operands is significant within an object
       definition.";
  }

  extension var {
    argument name;
    description
      "Definition of a VAR within an ADM.
       The argument to this statement is the object name.";
  }

  extension sbr {
    argument name;
    description
      "Definition of a SBR within an ADM.
       The argument to this statement is the object name.";
  }

  extension action {
    argument exec-tgt;
    description
      "Definition of the action executed by a rule object.
       The argument to this statement is the exec-tgt to execute.";
  }

  extension condition {
    argument expr;
    description
      "Condition evaluated by an SBR object to determine whether to
       execute its action.
       The argument to this statement is the expr to evaluate.";
  }

  extension min-interval {
    argument relative-time;
    description
      "The argument to this statement is a time-based ARI specifying
       the minimum amount of time between condition evaluations
       for an SBR object.";
  }

  extension max-count {
    argument count;
    description
      "The argument to this statement is the integer maximum
       execution count for a rule object.";
  }
  extension init-enabled {
    argument state;
    description
      "The argument to this statement is the boolean initial enabled
       state for a rule object.";
  }

  extension tbr {
    argument name;
    description
      "Definition of a TBR within an ADM.
       The argument to this statement is the object name.";
  }

  extension start {
    argument time;
    description
      "The argument to this statement is the start time ARI for a
       TBR object.";
  }

  extension period {
    argument relative-time;
    description
      "The argument to this statement is an ARI defining the period
       for a TBR object.";
  }

  /*
   * This section contains extensions for defining semantic type
   * instances.
   */

  extension display-hint {
    argument ident;
    description
      "Reference an IDENT object which indicates how a value should
       be displayed for human consumption.
       The base of the IDENT SHALL be the
       <ari://ietf/amm-base/ident/display-hint> object.";
  }

  extension int-labels {
    description
      "Type narrowing for an integer to label enum values or bit
       positions.";
  }

  extension cddl {
    argument text;
    description
      "Type narrowing for a CBOR item in the form of CDDL syntax.
       The argument to this statement is the actual CDDL text.";
  }

  extension ulist {
    description
      "Type for an AC containing a list of uniform-typed values.";
  }

  extension dlist {
    description
      "Type for an AC containing a list of diverse-typed sequences.";
  }

  extension seq {
    description
      "A sequence of uniform-typed values within a 'dlist'.";
  }

  extension umap {
    description
      "Type for an AM containing a set of uniform-typed key-value
       pairs.";
  }

  extension keys {
    description
      "The type restriction for 'umap' keys.";
  }

  extension values {
    description
      "The type restriction for 'umap' values.";
  }

  extension tblt {
    description
      "Type for a table of values with a column schema.";
  }
  extension column {
    argument name;
    description
      "An individual column within a 'tblt' definition.";
  }

  amm:enum 0;
}
